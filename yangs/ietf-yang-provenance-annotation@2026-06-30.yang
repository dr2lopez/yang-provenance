module ietf-yang-provenance-annotation {
  yang-version 1.1;
  namespace
    "urn:ietf:params:xml:ns:yang:ietf-yang-provenance-annotation";
  prefix ypmd;

  import ietf-yang-metadata {
    prefix md;
    reference
      "RFC 7952: Defining and Using Metadata with YANG";
  }
  import ietf-yang-provenance {
    prefix iyangprov;
    reference
      "RFC XXXX: Applying COSE Signatures for YANG Data Provenance";
  }

  organization "IETF OPSAWG (Operations and Management Area Working Group)";
  contact
    "WG Web:   <https://datatracker.ietf.org/wg/opsawg/>
    WG List:  <mailto:opsawg@ietf.org>

    Authors:  Diego Lopez
              <mailto:diego.r.lopez@telefonica.com>
              Alex Huang Feng
              <mailto:alex.huang-feng@t-systems.com>
              Antonio Pastor
              <mailto:antonio.pastorperales@telefonica.com>
              Henk Birkholz
              <mailto:henk.birkholz@sit.fraunhofer.de>";
    description
      "Defines a YANG metadata annotation for carrying provenance
      signatures on arbitrary YANG data elements.

      Copyright (c) 2026 IETF Trust and the persons identified as
      authors of the code.  All rights reserved.

      Redistribution and use in source and binary forms, with or without
      modification, is permitted pursuant to, and subject to the license
      terms contained in, the Revised BSD License set forth in Section
      4.c of the IETF Trust's Legal Provisions Relating to IETF Documents
      (https://trustee.ietf.org/license-info).

      This version of this YANG module is part of RFC XXXX; see the RFC
      itself for full legal notices.";

  revision 2026-06-30 {
    description
      "First revision";
    reference
      "RFC XXXX: Applying COSE Signatures for YANG Data Provenance";
  }

  md:annotation provenance {
    type iyangprov:provenance-signature;
    description
      "This annotation contains the provenance signature for
      the YANG element associated with it";
  }
}
